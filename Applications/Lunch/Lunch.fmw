FME workspace Lunch.fmw

Readers:
- ARCGISONLINEFEATURES_1: ARCGISONLINEFEATURES

Writers:
- ARCGISONLINEFEATURES_2: ARCGISONLINEFEATURES

Lunch (reader ARCGISONLINEFEATURES_1)
    attributes: objectid esriFieldTypeOID, globalid esriFieldTypeGlobalID(38), Name esriFieldTypeString(255), CuisineType esriFieldTypeString(13), CuisineType_other esriFieldTypeString(255), FoodType esriFieldTypeString(12), FoodType_other esriFieldTypeString(255), Rating esriFieldTypeString(1), CreationDate esriFieldTypeDate, Creator esriFieldTypeString(50), EditDate esriFieldTypeDate, Editor esriFieldTypeString(50), LastPicked esriFieldTypeDate
    -> JoinCreator
JoinCreator: AttributeCreator
    ATTR_TABLE = SET_TO join = 1
    -> Today
Today: DateTimeStamper
    DATETIME_ATTR = Today
    INCLUDE_OFFSET = YES
    STAMP_TYPE = datetime
    TIMEZONE = local
    -> DateCalculator
DateCalculator: DateTimeCalculator
    MODE = DATETIMECALC_1_ADD_INTERVAL
    OPERATION_PARAMETERS = START_DATETIME]@Value(Today)]OPERATOR]SUBTRACT]YEARS]0]MONTHS]0]DAYS]4]HOURS]0]MINUTES]0]SECONDS]0]RESULT_DATETIME]_result_datetime]FME_CONTROLLER_QUERY_FILE]transformers/dependencies/datetimecalculator/DATETIMECALC_1_ADD_INTERVAL.fme
    -> DateConverter
DateConverter: DateTimeConverter
    DATETIME_ATTR = Today
    OUT_FORMAT = %A
    REPAIR_INPUT = NO
    -> DayTester
DayTester: Tester
    BOOL_OP = COMPOSITE
    COMPOSITE_TEST = 1 OR 2 OR 3 OR 4
    TEST_CLAUSE:
      TEST @Value(Today) = Monday
      TEST @Value(Today) = Tuesday
      TEST @Value(Today) = Wednesday
      TEST @Value(Today) = Thursday
    PASSED -> Picker4DayTest
    FAILED -> Terminator
Picker4DayTest: Tester
    BOOL_OP = OR
    TEST_CLAUSE = TEST @Value(LastPicked) < @Value(_result_datetime)
    PASSED -> TempJoin [REQUESTOR]
Terminator
    MESSAGE = Translation Terminated
Creator
    COORDSYS = EPSG:4326
    GEOM = <?xml version="1.0" encoding="US_ASCII" standalone="no" ?><geometry><point><coord x="-117.5752011" y="34.1031981"/></point></geometry>
    GEOMTYPE = Geometry Object
    NUM = 1
    CREATED -> Weather [Point]
Weather: OpenWeatherMapForecaster
    APIKEY = 7dc061d29ef4036207f1b9a6bf573afe
    FORECASTTIMES = 09:00 06:00 21:00 18:00 03:00 00:00 15:00 12:00
    TYPE = Current
    UNITS = Fahrenheit
    Weather -> RemoveAll
RemoveAll: AttributeManager
    ATTR_TABLE:
      REMOVE location_name
      REMOVE location_latitude
      REMOVE location_longitude
      REMOVE location_country_code
      REMOVE datetime
      REMOVE temperature
      REMOVE temperature_min
      REMOVE pressure
      REMOVE pressure_at_sea_level
      REMOVE humidity
      REMOVE weather_id
      REMOVE weather_type
      REMOVE weather_description
      REMOVE weather_icon
      REMOVE clouds
      REMOVE wind_speed
      REMOVE wind_direction
      REMOVE rain_last_3_hours
      REMOVE snow_last_3_hours
      REMOVE units
      REMOVE location_sunrise
      REMOVE location_sunset
      REMOVE _creation_instance
      REMOVE _forecast_times
      SET_TO join = 1
    -> TempJoin [SUPPLIER]
TempJoin: FeatureMerger
    ATTR_ACCUM_MODE = Merge Supplier
    ATTR_CONFLICT_RES = Use Requestor
    IGNORE_NULLS = No
    JOIN_KEYS = @Value(join) @Value(join) AUTO
    MERGE_TYPE = Attributes Only
    PROCESS_DUPS = NO
    REJECT_NULL_MISSING_KEYS = No
    SUPPLIERS_FIRST = No
    MERGED -> WeatherTest
WeatherTest: TestFilter
    DEFAULT_VALUE = In between
    TEST_LIST = "BOOL_OP,OR,COMPOSITE_TEST,""""""<Unused>"""""",TEST_CLAUSE,TEST @Value(temperature_max) <= 65",65 or Below,"BOOL_OP,OR,COMPOSITE_TEST,""""""<Unused>"""""",TEST_CLAUSE,TEST @Value(temperature_max) > 85",Above 85
    In between -> Junction
    65 or Below -> Below65Weight
    Above 85 -> Above85Weight
Below65Weight: Tester
    BOOL_OP = OR
    TEST_CLAUSE = TEST @Value(FoodType) NOT_= Sandwitch
    PASSED -> Junction
Above85Weight: Tester
    BOOL_OP = AND
    TEST_CLAUSE:
      TEST @Value(CuisineType) NOT_= Vietnamese
      TEST @Value(CuisineType) NOT_= Thai
    PASSED -> Junction
Junction
    -> AttributePivoter
    -> FeatureMerger [SUPPLIER]
AttributePivoter
    GROUP_TOTALS_TAG = Total
    PIVOT_ATTR = Rating
    PIVOT_SUMMARY_TYPES = Average
    ROW_GROUP_ATTRS = Name
    DATA -> FeatureMerger [REQUESTOR]
FeatureMerger
    ATTR_ACCUM_MODE = Merge Supplier
    ATTR_CONFLICT_RES = Use Requestor
    CLEANING_TOLERANCE = None
    IGNORE_NULLS = No
    JOIN_KEYS = @Value(Name) @Value(Name) AUTO
    MERGE_TYPE = Attributes Only
    PROCESS_DUPS = No
    REJECT_NULL_MISSING_KEYS = No
    SUPPLIERS_FIRST = No
    MERGED -> AvgRatingTest
AvgRatingTest: Tester
    BOOL_OP = OR
    TEST_CLAUSE = TEST @Value(Rating) >= 3
    PASSED -> RandomNumber
RandomNumber: RandomNumberGenerator
    MAX = 100
    MIN = 0
    PLACES = 0
    RESULT_ATTR = _random_number
    -> ListBuilder
    -> MinNumber [SUPPLIER]
ListBuilder
    LIST_ATTRS_TO_INCLUDE = _random_number
    LIST_NAME = _list
    -> ListRangeExtractor
ListRangeExtractor
    MAX = _max
    MIN = _min
    SRC_LIST = _list{}._random_number
    -> MinNumber [REQUESTOR]
MinNumber: FeatureMerger
    ATTR_ACCUM_MODE = Merge Supplier
    ATTR_CONFLICT_RES = Use Requestor
    IGNORE_NULLS = No
    JOIN_KEYS = @Value(_min) @Value(_random_number) AUTO
    MERGE_TYPE = Attributes Only
    PROCESS_DUPS = NO
    REJECT_NULL_MISSING_KEYS = No
    SUPPLIERS_FIRST = No
    MERGED -> Emailer
    MERGED -> AttributeRemover
Emailer
    ATTACHGROUP = No
    BODY:
      DOIT Eats has chosen lunch today to be at: @Value(Name)

      @Value(Name) has an average rating of: @Value(Rating) Stars

      Today's Temp is: @Value(temperature_max)

      Please use the Survey 123 app called Lunch to rate your food and create new locations.
    FROM = DOIT_Eats@cityofrc.us
    SERVICE = Generic SMTP
    SMTP_CONNECTION = HOST;relay.cityofrc.us;PORT;25;ENCRYPTION;None;TIMEOUT;60;AUTHENTICATION;NO;USERNAME;<Unused>;PASSWORD;<Unused>;FME_CONTROLLER_QUERY_FILE;transformers\dependencies\emailer\Generic SMTP.fme
    SUBJECT = DOIT Eats Has Chosen Our Lunch Spot, We Are Going To: @Value(Name)
    TO = doit_eats@cityofrc.us
AttributeRemover
    LIST_ATTRS = _list{} _list{}._random_number
    REMOVE_ATTRS = Today,_min,CuisineType,LastPicked,join,Name,_max,CreationDate,globalid,CuisineType_other,Creator,EditDate,Editor,Rating,_random_number,FoodType,FoodType_other
    -> LastPickDate
LastPickDate: DateTimeStamper
    DATETIME_ATTR = LastPicked
    INCLUDE_OFFSET = NO
    STAMP_TYPE = datetime
    TIMEZONE = utc
    -> Lunch (writer ARCGISONLINEFEATURES_2)
Lunch (writer ARCGISONLINEFEATURES_2)
    attributes: objectid esriFieldTypeOID, globalid esriFieldTypeGlobalID(38), Name esriFieldTypeString(255), CuisineType esriFieldTypeString(13), CuisineType_other esriFieldTypeString(255), FoodType esriFieldTypeString(12), FoodType_other esriFieldTypeString(255), Rating esriFieldTypeString(1), CreationDate esriFieldTypeDate, Creator esriFieldTypeString(50), EditDate esriFieldTypeDate, Editor esriFieldTypeString(50), LastPicked esriFieldTypeDate

FME custom transformer OpenWeatherMapForecaster
gets current weather conditions or 5 days weather forecast for the location of the input point. 
    The transformer uses OpenWeatherMap (
        http://openweathermap.org/
    ) API. 
    Input
    Point
    The transformer works with points and rejects all other geometries. The service requires the points in Latitude/Longitude, so if the source points have a coordinate system assigned, they will be reprojected. If the points don't have a coordinate system, LL84 will be assumed, and, if the coordinates of the points don't fit into the proper ranges ([-180..180][-90..90]), they will be output through <Rejected> port. 
    Output
    Weather
    The transformer outputs points with the weather information stored in the attributes. For 5 days forecast, a separate point is output for each specified date/time during the upcoming 5 days (up to 40 output points per single input). The following attributes are added to the features:
    clouds
    (%)
    humidity 
    (%)
    location_country_code 
    location_latitude 
    location_longitude 
    location_name 
    location_sunrise
    (for current conditions only, UTC)
    location_sunset 
    (for current conditions only, UTC)
    pressure 
    (hPa)
    pressure_at_sea_level 
    (hPa)
    rain_last_3_hours 
    snow_last_3_hours 
    temperature 
    temperature_max 
    temperature_min 
    units 
    weather_description 
    weather_icon 
    (a url of a WeatherOpenMap icon for the weather)
    weather_id 
    weather_type 
    wind_direction 
    wind_speed 
    (m/s for Celsius, miles/hour for Fahrenheit)
    <Rejected> 
    Non-point features and points outside of the valid range of coordinates are output through this port.
    Parameters
    OpenWeatherMap API Key
    - an API key needed for accesing the weather service. Sign up here - 
        http://openweathermap.org/appid
    Units
    - Celsius or Fahrenheit. This parameter also defines, in which units the wind speed is reported (m/s or miles/hour)
    Weather
    - either current conditions or the 5 days forecast
    Forecast Time
    - times, for which the forecast should be reported (every three hours starting from noon)
    Example
        https://hub.safe.com/templates/weatherstationpublicexample
    Usage notes
    Make sure you comply with the terms and conditons of the service - 
        http://openweathermap.org/

Parameters:
- APIKEY =   # OpenWeatherMap API Key
- UNITS = Celsius   # Units
- TYPE = Current   # days Forecast" Weather
- FORECASTTIMES = 12:00   # Forecast Time

Point (input)
    -> GeometryFilter
Note: Make sure the input consists of points only. / Reject other geometries
GeometryFilter
    BREAK_AGG = No
    GEOM_PORT_NAMES = Point
    POINT -> Reprojector
    <UNFILTERED> -> AttributeCreator_4
Note: Reproject to LL84 required by the weather service
Reprojector
    DEST = LL84
    INTERPOLATION_TYPE_NAME = Nearest Neighbor
    RASTER_CELL_SIZE = Preserve Cells
    RASTER_TOLERANCE = 0.0
    SOURCE = Read from feature
    REPROJECTED -> CoordinateExtractor
CoordinateExtractor
    IND = 0
    MODE = Specify Coordinate
    X_ATTR = _lon
    Y_ATTR = _lat
    Z_ATTR = _z
    -> Tester_3
Note: If the source points don't have a coordinate system set, / but are supposed to be in LL, / reject points with bad coordinates (out of range)
Tester_3
    BOOL_OP = AND
    TEST_CLAUSE:
      TEST @Value(_lat) >= -90
      TEST @Value(_lat) <= 90
      TEST @Value(_lon) >= -180
      TEST @Value(_lon) <= 180
    PASSED -> AttributeCreator_3
    FAILED -> AttributeCreator_6
Note: Create degree units - Celcius or Fahrenheit (metric or imperial)
AttributeCreator_3
    ATTR_TABLE = SET_TO _units_url = FME_CONDITIONAL:DEFAULT_VALUE'_FME_NO_OP_'BOOL_OP;OR;COMPOSITE_TEST;<Unused>;TEST $(UNITS) = Celsius'units=metric'BOOL_OP;OR;COMPOSITE_TEST;<Unused>;TEST $(UNITS) = Fahrenheit'units=imperial'FME_NUM_CONDITIONS3___
    -> Decelerator
Note: Send 1 feature per second to avoid service rule violations / (60 requests per minute for free account. / Paid accounts have higher limits: / http://openweathermap.org/price
Decelerator
    DECEL_TYPE = Limit Features Per Second
    FEATURES_PER_SECOND = 1
    -> Tester
Note: Current conditions or forecast?
Tester
    BOOL_OP = OR
    TEST_CLAUSE = TEST $(TYPE) = Current
    PASSED -> AttributeCreator_5
    PASSED -> AttributeCreator
    FAILED -> AttributeCreator_2
StringFormatter
    FORMAT = .1f
    SRC_ATTRS = temperature_max,temperature,temperature_min
    -> Weather (output)
Weather (output)
<Rejected> (output)

Bookmark: Current Conditions
Note: By postal code/zip code. Deactivated in this transformer
AttributeCreator_5 [off]
    ATTR_TABLE = SET_TO _weather_url = http://api.openweathermap.org/data/2.5/weather?zip=49124,de&@Value(_units_url)&appid=e89183a6b4b2f8f41e85172ebec64855
    -> HTTPCaller
Note: Make url
AttributeCreator
    ATTR_TABLE = SET_TO _weather_url = http://api.openweathermap.org/data/2.5/weather?lat=@Value(_lat)&lon=@Value(_lon)&@Value(_units_url)&appid=$(APIKEY)
    -> HTTPCaller
Note: Submit url
HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = _weather_json
    TARGET_ATTR_ENCODING = auto-detect
    TARGET_URL = @Value(_weather_url)
    TRANSFER_TIMEOUT_LENGTH = 90
    USE_COOKIES = No
    VERIFY_SSL_CERTIFICATES = Yes
    -> JSONExtractor_3
Note: Extract attributes from JSON response
JSONExtractor_3
    EXTRACT_QUERY_TABLE = location_name json["name"] location_latitude json["coord"]["lat"] location_longitude json["coord"]["lon"] location_country_code json["sys"]["country"] location_sunrise json["sys"]["sunrise"] location_sunset json["sys"]["sunset"] datetime json["dt"] temperature json["main"]["temp"] temperature_min json["main"]["temp_min"] temperature_max json["main"]["temp_max"] pressure json["main"]["pressure"] pressure_at_sea_level json["main"]["sea_level"] humidity json["main"]["humidity"] weather_id json["weather"][*]["id"] weather_type json["weather"][*]["main"] weather_description json["weather"][*]["description"] weather_icon json["weather"][*]["icon"] clouds json["clouds"]["all"] wind_speed json["wind"]["speed"] wind_direction json["wind"]["deg"] rain_last_3_hours json["rain"]["3h"] snow_last_3_hours json["snow"]["3h"]
    JSON_DOCUMENT = @Value(_weather_json)
    EVALUATED -> AttributeManager_2
AttributeManager_2
    ATTR_TABLE:
      REMOVE _weather_url
      REMOVE _lon
      REMOVE _lat
      REMOVE _z
      REMOVE _weather_json
      REMOVE _http_status_code
      SET_TO weather_icon = http://openweathermap.org/img/w/@Value(weather_icon).png
      REMOVE _units_url
      SET_TO units = $(UNITS)
    -> DateFormatter
DateFormatter
    DATE_ATTR = location_sunset,datetime,location_sunrise
    FMT = %Y-%m-%d %H:%M:%S
    INVALID_DATE_VALUE = _FME_NO_OP_
    SRCFMT = %s
    -> StringFormatter

Bookmark: Five Days Forecast
Note: Make url
AttributeCreator_2
    ATTR_TABLE = SET_TO _weather_url = http://api.openweathermap.org/data/2.5/forecast?lat=@Value(_lat)&lon=@Value(_lon)&@Value(_units_url)&appid=$(APIKEY)
    -> HTTPCaller_2
Note: Submit url
HTTPCaller_2
    CONNECTION_TIMEOUT_LENGTH = 60
    ERROR_ATTR = _error
    FOLLOW_REDIRECTS = Yes
    HTTP_METHOD = GET
    SAVE_FILE = Attribute
    STATUS_CODE_ATTR = _http_status_code
    TARGET_ATTR = _weather_json
    TARGET_ATTR_ENCODING = auto-detect
    TARGET_URL = @Value(_weather_url)
    TRANSFER_TIMEOUT_LENGTH = 90
    USE_COOKIES = No
    VERIFY_SSL_CERTIFICATES = Yes
    -> JSONExtractor
DateFormatter_2
    DATE_ATTR = datetime_for_filter
    FMT = %H:00
    INVALID_DATE_VALUE = _FME_NO_OP_
    SRCFMT = %Y-%m-%d %H:%M:%S
    -> ParameterFetcher_2
Note: Get forecast times
ParameterFetcher_2
    ATTR_LIST = _forecast_times $(FORECASTTIMES)
    -> StringReplacer
StringReplacer
    CASE = NO
    FIND_TEXT = " "
    NO_MATCH = _FME_NO_OP_
    REGEXP = NO
    REPLACE_TEXT = ,
    SRC_ATTRS = _forecast_times
    -> Tester_2
Note: Pass through only selected times
Tester_2
    BOOL_OP = OR
    TEST_CLAUSE = TEST @Value(datetime_for_filter) IN @Value(_forecast_times)
    PASSED -> AttributeManager
AttributeManager
    ATTR_TABLE:
      REMOVE _weather_url
      REMOVE _lon
      REMOVE _lat
      REMOVE _z
      REMOVE _weather_json
      REMOVE _http_status_code
      REMOVE json_type
      REMOVE json_index
      SET_TO weather_icon = http://openweathermap.org/img/w/@Value(weather_icon).png
      REMOVE _units_url
      SET_TO units = $(UNITS)
      REMOVE datetime_for_filter
    -> Sorter
Note: make sure date/time order is correct
Sorter
    SORT_PARM = datetime ALPHA ASCENDING
    SORTED -> StringFormatter

Bookmark: Extract attributes from JSONresponse
JSONExtractor
    EXTRACT_QUERY_TABLE = location_name json["city"]["name"] location_latitude json["city"]["coord"]["lat"] location_longitude json["city"]["coord"]["lon"] location_country_code json["city"]["country"]
    JSON_DOCUMENT = @Value(_weather_json)
    EVALUATED -> JSONFragmenter
JSONFragmenter
    EXPLODE_FORMAT = JSON
    EXTRACT_ATTR = No
    JSON_ATTR = _weather_json
    JSON_QUERY = json["list"][*]
    FRAGMENTS -> JSONExtractor_2
JSONExtractor_2
    EXTRACT_QUERY_TABLE = datetime json["dt_txt"] datetime_for_filter json["dt_txt"] temperature json["main"]["temp"] temperature_min json["main"]["temp_min"] temperature_max json["main"]["temp_max"] pressure json["main"]["pressure"] pressure_at_sea_level json["main"]["seal_level"] humidity json["main"]["humidity"] weather_id json["weather"][*]["id"] weather_type json["weather"][*]["main"] weather_description json["weather"][*]["description"] weather_icon json["weather"][*]["icon"] clouds json["clouds"]["all"] wind_speed json["wind"]["speed"] wind_direction json["wind"]["deg"] rain_last_3_hours json["rain"]["3h"] snow_last_3_hours json["snow"]["3h"]
    JSON_DOCUMENT = @Value(_weather_json)
    EVALUATED -> DateFormatter_2

Bookmark: Rejection messages
AttributeCreator_6
    ATTR_TABLE = SET_TO _rejection_message = Coordinates out of range
    -> <Rejected> (output)
AttributeCreator_4
    ATTR_TABLE = SET_TO _rejection_message = The feature is not a point
    -> <Rejected> (output)
