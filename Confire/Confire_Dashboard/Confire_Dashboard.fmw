FME workspace Confire_Dashboard.fmw
Shutdown Python:
      import smtplib, fmeobjects, os

      #Specify runtime variables
      Workspace_Name = FME_MacroValues['FME_MF_NAME']
      SMTP_Host = 'relay.cityofrc.us'
      Send_To = 'Ryan.Wilson@cityofrc.us'
      Send_From = 'Confire_Dashboard@RCV00219.local'

      #Get number of features FME wrote
      FeaturesWritten = str(FME_FeaturesWritten)

      # If FME Fails then Change Subject, if success also rename the source CSV files so we dont process again
      status = FME_Status
      if status == 0:
          if (not os.path.isfile('//rcv00143/d/Projects/Confire/Failed.txt')):
             add = open('//rcv00143/d/Projects/Confire/Failed.txt','a')
             add.write('1')
             add.close()
             last = '1'
          else:
             read = open('//rcv00143/d/Projects/Confire/Failed.txt','r')
             r = read.readlines()
             last = r[len(r)-1]
             read.close()
             if last >='4':
                Subject =  'Confire_Dashboard: FAILED - ' + Workspace_Name
                Message = 'Workspace Failed: ' + Workspace_Name + ' - ' + FME_FailureMessage
                # Send the email
                smtpserver = smtplib.SMTP(SMTP_Host,25)
                smtpserver.ehlo()
                #smtpserver.starttls()
                #smtpserver.ehlo
                header = 'To:' + Send_To + '\n' + 'From: ' + Send_From + '\n' + 'Subject:' + Subject +'\n'
                print header
                msg = header + '\n' + Message + '\n\n'
                smtpserver.sendmail(Send_From, Send_To, msg)
                smtpserver.close()
             else:
                add = open('//rcv00143/d/Projects/Confire/Failed.txt','a')
                nex = int(last) + 1
                add.write('\n'+str(nex))
                add.close()
      else:
          if os.path.isfile('//rcv00143/d/Projects/Confire/Failed.txt'):
             os.remove('//rcv00143/d/Projects/Confire/Failed.txt')

      print 'Done'

Parameters:
- SourceDataset_MSSQL_ADO_3 = System   # Database
- SourceDataset_MSSQL_ADO_4 = System   # Database
- SourceDataset_ARCGISONLINEFEATURES = www.arcgis.com   # Host
- SourceDataset_ARCGISONLINEFEATURES_5 = www.arcgis.com   # Host
- Date:   # Python Script
      import datetime, time
      today = datetime.date.today()
      day = datetime.timedelta(days=3)
      yesterday = today - day
      date_format = yesterday.strftime("%m/%d/%Y")
      datestring = "Response_Date > '" + date_format + "'"
      return(datestring)

Readers:
- MSSQL_ADO_1: MSSQL_ADO from $(SourceDataset_MSSQL_ADO_3) in EPSG:4326
- MSSQL_ADO_2: MSSQL_ADO from $(SourceDataset_MSSQL_ADO_4) in EPSG:4326
- ARCGISONLINEFEATURES_1: ARCGISONLINEFEATURES from $(SourceDataset_ARCGISONLINEFEATURES) in EPSG:3857
- ARCGISONLINEFEATURES_2: ARCGISONLINEFEATURES from $(SourceDataset_ARCGISONLINEFEATURES_5) in EPSG:3857
- ARCGISONLINEFEATURES_4: ARCGISONLINEFEATURES

Writers:
- ARCGISONLINEFEATURES_5: ARCGISONLINEFEATURES
- ARCGISONLINEFEATURES_6: ARCGISONLINEFEATURES
- ARCGISONLINEFEATURES_7: ARCGISONLINEFEATURES
- ARCGISONLINEFEATURES_8: ARCGISONLINEFEATURES
- ARCGISONLINEFEATURES_9: ARCGISONLINEFEATURES

Bookmark: Readers
Note: 48 Hours of Apparatus Data from 911 Dispatch
CONFIRE_GISDailyIncidentVehicles (reader MSSQL_ADO_2)
    attributes: Master_Incident_Number varchar(20), Response_Date datetime, VEHICLE ID integer, VEHICLE Master_Incident_ID integer, VEHICLE Agency_Type varchar(30), VEHICLE Jurisdiction varchar(30), VEHICLE Division varchar(30), VEHICLE Radio_Name varchar(20), VEHICLE Vehicle_ID integer, VEHICLE FR_MA_AA_Flag varchar(2), VEHICLE Time_PreAssigned datetime, VEHICLE Time_Assigned datetime, VEHICLE Time_Enroute datetime, VEHICLE Time_ArrivedAtScene datetime, VEHICLE Time_Staged datetime, VEHICLE Time_Contact datetime, VEHICLE Time_Delayed_Availability datetime, VEHICLE Time_Call_Cleared datetime, VEHICLE Time_BackInQtrs datetime, VEHICLE Elapsed_Assigned_2_Enroute varchar(10), VEHICLE Elapsed_Enroute_2_Arrival varchar(10), VEHICLE Elapsed_Assigned_2_Clear varchar(10), VEHICLE Fixed_Time_PreAssigned datetime, VEHICLE Fixed_Time_Assigned datetime, VEHICLE Fixed_Time_Enroute datetime, VEHICLE Fixed_Time_ArrivedAtScene datetime, VEHICLE Fixed_Time_Staged datetime, VEHICLE Fixed_Time_Contact datetime, VEHICLE Fixed_Time_DelayedAvailable datetime, VEHICLE Fixed_Time_Call_Cleared datetime,
      VEHICLE Fixed_Time_BackInQtrs datetime, VEHICLE Cancel_Reason varchar(30), VEHICLE Delay_Reason varchar(30), VEHICLE Location_At_Assign_Time varchar(400), VEHICLE Longitude_At_Assign_Time varchar(10), VEHICLE Latitude_At_Assign_Time varchar(10), VEHICLE Vehicle_Info_ID integer, VEHICLE Number_Of_Victims_Seen integer, VEHICLE Refusal_Number varchar(15), VEHICLE Crew_Tckt_Nmbr varchar(15), VEHICLE Call_Disposition varchar(30), VEHICLE Time_Avail_AtScene datetime, VEHICLE Fixed_Time_Avail_AtScene datetime, VEHICLE Avail_AtScene_Performed_By varchar(80), VEHICLE Cancel_Type varchar(10), VEHICLE Response_Number varchar(20), VEHICLE Calculate_ETA datetime, VEHICLE Check_Assign_Flag tinyint, VEHICLE Status_ID integer, VEHICLE TimeStatusChanged datetime, VEHICLE LateFlag bit, VEHICLE PrimaryVehicleFlag bit, VEHICLE AlarmLevel integer, VEHICLE Current_UnitRespPriorityCode varchar(10), VEHICLE Current_UnitRespPriorityDesc varchar(30), VEHICLE TimeMoveAfterResponding datetime
    -> RemovedDashFromAppNum
Note: 48 Hours of Incident Data from 911 Dispatch
CONFIRE_GISDailyIncidents (reader MSSQL_ADO_1)
    attributes: ID identity, Master_Incident_Number varchar(20), Response_Date datetime, Agency_Type varchar(30), Jurisdiction varchar(30), Division varchar(30), Response_Area varchar(30), Response_Time_Criteria varchar(8), Response_Plan varchar(30), Incident_Type varchar(30), Problem varchar(30), Priority_Number integer, Priority_Description varchar(30), Location_Name varchar(400), Address varchar(400), Apartment varchar(10), City varchar(35), State varchar(5), Postal_Code varchar(10), County varchar(30), Location_Type varchar(30), Longitude varchar(10), Latitude varchar(10), Map_Info varchar(10), Cross_Street varchar(400), Time_PhonePickUp datetime, Time_FirstCallTakingKeystroke datetime, Time_CallEnteredQueue datetime, Time_CallTakingComplete datetime, Time_Incident_Under_Control datetime,
      Time_CallClosed datetime, Time_First_Unit_Assigned datetime, Time_First_Unit_Enroute datetime, Time_First_Unit_Arrived datetime, Elapsed_CallRcvd2InQueue varchar(10), Elapsed_CallRcvd2CalTakDone varchar(10), Elapsed_InQueue_2_FirstAssign varchar(10), Elapsed_CallRcvd2FirstAssign varchar(10), Elapsed_Assigned2FirstEnroute varchar(10), Elapsed_Enroute2FirstAtScene varchar(10), Elapsed_CallRcvd2CallClosed varchar(10), Fixed_Time_PhonePickUp datetime, Fixed_Time_CallEnteredQueue datetime, Fixed_Time_CallTakingComplete datetime, Fixed_Time_CallClosed datetime, Fixed_Time_SentToOtherCAD datetime, EMD_Used smallint, Determinant varchar(10), ProQa_CaseNumber varchar(10), Call_Disposition varchar(30), Cancel_Reason varchar(30), Building varchar(10), Call_Is_Active integer, Delay_Reason varchar(30), Street_ID integer, PremiseID integer, ClockStartTime datetime, Call_Orig_OnHold datetime, Call_Final_OffHold datetime, House_Number varchar(10),
      Prefix_Directional varchar(22), Name_Component varchar(150), Street_Type varchar(15), Post_Directional varchar(22), TimeFirstStaged datetime, TimeFirstPTContact datetime, TimeFirstDelayedAvail datetime, TimeFirstCallCleared datetime, CautionNote bit, HazmatNote bit, PremiseHistory bit, CurrentDivision varchar(30), IntersectionStreetID integer
    -> InitialDataCleanup [RemoveDashFromIncidentNum_Input]
Dashboard_Incidents (reader ARCGISONLINEFEATURES_4)
    attributes: OBJECTID esriFieldTypeOID, ID esriFieldTypeInteger, Master_Incident_Number esriFieldTypeString(20), Response_Date esriFieldTypeDate, Jurisdiction esriFieldTypeString(30), Division esriFieldTypeString(30), Response_Area esriFieldTypeString(30), Response_Plan esriFieldTypeString(30), Incident_Type esriFieldTypeString(30), Problem esriFieldTypeString(30), Priority_Number esriFieldTypeInteger, Priority_Description esriFieldTypeString(30), Location_Name esriFieldTypeString(400), Address esriFieldTypeString(400), Apartment esriFieldTypeString(10), City esriFieldTypeString(35), State esriFieldTypeString(5), Postal_Code esriFieldTypeString(10), County esriFieldTypeString(30), Location_Type esriFieldTypeString(30), Longitude esriFieldTypeDouble, Latitude esriFieldTypeDouble, Map_Info esriFieldTypeString(10), Cross_Street esriFieldTypeString(400), Time_CallClosed esriFieldTypeDate, EMD_Used esriFieldTypeSmallInteger, Determinant esriFieldTypeString(10), Building esriFieldTypeString(10), Call_Is_Active esriFieldTypeInteger, CallCode esriFieldTypeString(10),
      DeterminantCode esriFieldTypeString(10), Status esriFieldTypeString(8), Symbology esriFieldTypeString(8), GlobalID esriFieldTypeGlobalID(38), Units esriFieldTypeString(200), Appr_Divs esriFieldTypeString(200)
    -> FeatureMerger_3 [SUPPLIER]
Dashboard_Apparatus (reader ARCGISONLINEFEATURES_4)
    attributes: OBJECTID esriFieldTypeOID, Master_Incident_Number esriFieldTypeString(20), Response_Date esriFieldTypeDate, Division esriFieldTypeString(30), Radio_Name esriFieldTypeString(20), Longitude esriFieldTypeDouble, Latitude esriFieldTypeDouble, Hour_ esriFieldTypeSmallInteger, GlobalID esriFieldTypeGlobalID(38), Inc_Division esriFieldTypeString(30)
    -> FeatureMerger_4 [SUPPLIER]

Bookmark: Transformers
Note: Remove the Dash from the Incident Number
RemovedDashFromAppNum: StringReplacer
    REGEXP = no
    NO_MATCH = _FME_NO_OP_
    FIND_TEXT = -
    CASE = no
    SRC_ATTRS = Master_Incident_Number
    -> ListCreator [AttributeRenamer_ApparatusID_Input]
    -> AttributeRemover
Note: Create Apparatus Unit List
ListCreator: UnitCreator
    VEHICLE_DIVISION = @Value(VEHICLE Division)
    VEHICLE_RADIO_NAME = @Value(VEHICLE Radio_Name)
    MASTER_INCIDENT_NUMBER = @Value(Master_Incident_Number)
    AttributeRemover_2_Output -> FeatureMerger_2 [SUPPLIER]
Note: Remove Attributes no longer needed
AttributeRemover
    REMOVE_ATTRS = VEHICLE Agency_Type,VEHICLE AlarmLevel,VEHICLE Avail_AtScene_Performed_By,VEHICLE Calculate_ETA,VEHICLE Call_Disposition,VEHICLE Cancel_Reason,VEHICLE Cancel_Type,VEHICLE Check_Assign_Flag,VEHICLE Crew_Tckt_Nmbr,VEHICLE Current_UnitRespPriorityCode,VEHICLE Current_UnitRespPriorityDesc,VEHICLE Delay_Reason,VEHICLE Elapsed_Assigned_2_Clear,VEHICLE Elapsed_Assigned_2_Enroute,VEHICLE Elapsed_Enroute_2_Arrival,VEHICLE Fixed_Time_ArrivedAtScene,VEHICLE Fixed_Time_Assigned,VEHICLE Fixed_Time_Avail_AtScene,VEHICLE Fixed_Time_BackInQtrs,VEHICLE Fixed_Time_Call_Cleared,VEHICLE Fixed_Time_Contact,VEHICLE Fixed_Time_DelayedAvailable,VEHICLE Fixed_Time_Enroute,VEHICLE Fixed_Time_PreAssigned,VEHICLE Fixed_Time_Staged,VEHICLE FR_MA_AA_Flag,VEHICLE ID,VEHICLE Jurisdiction,VEHICLE LateFlag,VEHICLE Latitude_At_Assign_Time,VEHICLE Location_At_Assign_Time,VEHICLE Longitude_At_Assign_Time,VEHICLE Master_Incident_ID,VEHICLE Number_Of_Victims_Seen,VEHICLE PrimaryVehicleFlag,VEHICLE Refusal_Number,VEHICLE Response_Number,VEHICLE Status_ID,VEHICLE Time_ArrivedAtScene,VEHICLE Time_Assigned,VEHICLE Time_Avail_AtScene,VEHICLE Time_BackInQtrs,VEHICLE Time_Call_Cleared,VEHICLE Time_Contact,VEHICLE Time_Delayed_Availability,VEHICLE Time_Enroute,VEHICLE Time_PreAssigned,VEHICLE Time_Staged,VEHICLE TimeMoveAfterResponding,VEHICLE TimeStatusChanged,VEHICLE Vehicle_ID,VEHICLE Vehicle_Info_ID
    -> FeatureMerger [REQUESTOR]
Note: Remove eronious data that will not be needed
InitialDataCleanup
    MASTER_INCIDENT_NUMBER = @Value(Master_Incident_Number)
    LATITUDE = @Value(Latitude)
    INCIDENT_TYPE = @Value(Incident_Type)
    RemoveBlankIncidentsandTests_Failed -> Incident_Coordinate_Fix [Stripped_Lat_Front_Input]
Note: Fix XY Coordinates
Incident_Coordinate_Fix: Incident Coordinate Fix
    LATITUDE = @Value(Latitude)
    LONGITUDE = @Value(Longitude)
    AttributeRemover_Output -> DashboardAttributeCreator [AttributeCreator_Input]
    AttributeRemover_Output -> Junction
Junction
    -> Junction_2
Junction_2
    -> AttributeRemoverInc
Note: Remove Attreibutes not needed from Incidents
AttributeRemoverInc
    REMOVE_ATTRS = Address,Apartment,Building,Call_Is_Active,City,County,Cross_Street,Determinant,EMD_Used,ID,Incident_Type,Jurisdiction,Location_Name,Location_Type,Map_Info,Postal_Code,Priority_Description,Priority_Number,Problem,Response_Area,Response_Date,Response_Plan,State,Time_CallClosed
    -> AttributeRenamerInc_Division
Note: Renamed Inc_Division field
AttributeRenamerInc_Division
    ATTR_LIST = Division,Inc_Division,@Value(Division)
    -> FeatureMerger [SUPPLIER]
FeatureMerger
    JOIN_KEYS = @Value(Master_Incident_Number) @Value(Master_Incident_Number) AUTO
    SUPPLIERS_FIRST = No
    IGNORE_NULLS = No
    MERGE_TYPE = Attributes Only
    ATTR_CONFLICT_RES = Use Requestor
    ATTR_ACCUM_MODE = Merge Supplier
    PROCESS_DUPS = No
    MERGED -> AttributeRenamer
Note: Renamed Attributes to match AGOL
AttributeRenamer
    ATTR_LIST = VEHICLE Division,Division,@Value(VEHICLE Division),VEHICLE Radio_Name,Radio_Name,@Value(VEHICLE Radio_Name)
    -> CreateHourAttribute [AttributeCreator_3_Input]
Note: Create and Populate Hour Field
CreateHourAttribute
    RESPONSE_DATE = @Value(Response_Date)
    StringFormatter_Hour_Output -> CreateAppPoint
Note: Create Points based on XY Coord
CreateAppPoint: VertexCreator
    INDEX = 0
    YVAL = @Value(Latitude)
    XVAL = @Value(Longitude)
    MODE_NAME = Add Point
    -> FeatureMerger_4 [REQUESTOR]
Note: Add fields needed for the dashboard
DashboardAttributeCreator
    EMD_USED = @Value(EMD_Used)
    CALL_IS_ACTIVE = @Value(Call_Is_Active)
    DETERMINANT = @Value(Determinant)
    INCIDENT_TYPE = @Value(Incident_Type)
    AttributeCreator_2_Output -> FeatureMerger_2 [REQUESTOR]
FeatureMerger_2
    JOIN_KEYS = @Value(Master_Incident_Number) @Value(Master_Incident_Number) AUTO
    SUPPLIERS_FIRST = No
    IGNORE_NULLS = No
    MERGE_TYPE = Attributes Only
    ATTR_CONFLICT_RES = Use Requestor
    ATTR_ACCUM_MODE = Merge Supplier
    PROCESS_DUPS = No
    MERGED -> UnitCutoff
    NOT_MERGED -> AddUnitNotMerged
AddUnitNotMerged: AttributeCreator
    ATTR_LIST = Units,"",Appr_Divs,""
    -> UnitCutoff
Note: Units field cut to 200 characters
UnitCutoff: SubstringExtractor
    SRC_STRING = @Value(Units)
    START = 0
    RESULT_ATTR = Units
    END = 199
    -> Appr_DivsCutoff
Note: App_Div field cut to 200 characters
Appr_DivsCutoff: SubstringExtractor
    SRC_STRING = @Value(Appr_Divs)
    START = 0
    RESULT_ATTR = Appr_Divs
    END = 199
    -> CreateIncidentPoint
Note: Create Points based on XY Coord
CreateIncidentPoint: VertexCreator
    INDEX = 0
    YVAL = @Value(Latitude)
    XVAL = @Value(Longitude)
    MODE_NAME = Add Point
    -> FeatureMerger_3 [REQUESTOR]
FeatureMerger_3
    JOIN_KEYS = @Value(Master_Incident_Number) @Value(Master_Incident_Number) AUTO
    SUPPLIERS_FIRST = No
    IGNORE_NULLS = No
    MERGE_TYPE = Attributes Only
    ATTR_CONFLICT_RES = Use Requestor
    ATTR_ACCUM_MODE = Merge Supplier
    PROCESS_DUPS = No
    MERGED -> Inc12HourSelection_2 [DateFormatter_Input]
    NOT_MERGED -> AttributeCreator
    NOT_MERGED -> IncConvertUTCNotMerged [DateFormatter_7_Input]
    DUPLICATE_SUPPLIER -> Dashboard_Incidents (writer ARCGISONLINEFEATURES_5)
Note: Update only the last 12 hours of Data
Inc12HourSelection_2: Month Selection
    RESPONSE_DATE = @Value(Response_Date)
    AttributeCreator_Output -> IncConveretUTCMerged [DateFormatter_7_Input]
Note: Convert Date to UTC
IncConveretUTCMerged: UTC Converter
    RESPONSE_DATE = @Value(Response_Date)
    TCLCaller_4_Output -> Dashboard_Incidents (writer ARCGISONLINEFEATURES_7)
Note: Convert Date to UTC
IncConvertUTCNotMerged: UTC Converter
    RESPONSE_DATE = @Value(Response_Date)
    TCLCaller_4_Output -> Dashboard_Incidents (writer ARCGISONLINEFEATURES_6)
AttributeCreator
    ATTR_TABLE:
      SET_TO DayofWeek = @Value(Response_Date)
      SET_TO NumofWeek = @Value(Response_Date)
    -> DateFormatter
DateFormatter
    SRCFMT = %Y%m%d%H%M%S
    INVALID_DATE_VALUE = _FME_NO_OP_
    FMT = %A
    DATE_ATTR = DayofWeek
    -> DateFormatter_4
DateFormatter_4
    SRCFMT = %Y%m%d%H%M%S
    INVALID_DATE_VALUE = _FME_NO_OP_
    FMT = %u
    DATE_ATTR = NumofWeek
    -> Dashboard_Incidents (writer ARCGISONLINEFEATURES_8)
FeatureMerger_4
    JOIN_KEYS = @Value(Master_Incident_Number) @Value(Master_Incident_Number) AUTO @Value(Radio_Name) @Value(Radio_Name) AUTO
    SUPPLIERS_FIRST = No
    IGNORE_NULLS = No
    MERGE_TYPE = Attributes Only
    ATTR_CONFLICT_RES = Use Requestor
    ATTR_ACCUM_MODE = Merge Supplier
    PROCESS_DUPS = No
    MERGED -> App12HourSelection [DateFormatter_Input]
    NOT_MERGED -> AttributeCreator_2
    NOT_MERGED -> AppConvertUTCNotMerged [DateFormatter_7_Input]
    DUPLICATE_SUPPLIER -> Dashboard_Apparatus (writer ARCGISONLINEFEATURES_5)
Note: Update only the last 12 hours of Data
App12HourSelection: Month Selection
    RESPONSE_DATE = @Value(Response_Date)
    AttributeCreator_Output -> AppConvertUTCMerged [DateFormatter_7_Input]
Note: Convert Date to UTC
AppConvertUTCMerged: UTC Converter
    RESPONSE_DATE = @Value(Response_Date)
    TCLCaller_4_Output -> Dashboard_Apparatus (writer ARCGISONLINEFEATURES_7)
Note: Convert Date to UTC
AppConvertUTCNotMerged: UTC Converter
    RESPONSE_DATE = @Value(Response_Date)
    TCLCaller_4_Output -> Dashboard_Apparatus (writer ARCGISONLINEFEATURES_6)
AttributeCreator_2
    ATTR_TABLE:
      SET_TO DayofWeek = @Value(Response_Date)
      SET_TO NumofWeek = @Value(Response_Date)
    -> DateFormatter_2
DateFormatter_2
    SRCFMT = %Y%m%d%H%M%S
    INVALID_DATE_VALUE = _FME_NO_OP_
    FMT = %A
    DATE_ATTR = DayofWeek
    -> DateFormatter_3
DateFormatter_3
    SRCFMT = %Y%m%d%H%M%S
    INVALID_DATE_VALUE = _FME_NO_OP_
    FMT = %u
    DATE_ATTR = NumofWeek
    -> Dashboard_Apparatus (writer ARCGISONLINEFEATURES_9)

Bookmark: Writers
Note: Confire Incidents Updated
Dashboard_Incidents (writer ARCGISONLINEFEATURES_7)
    attributes: OBJECTID esriFieldTypeOID, ID esriFieldTypeInteger, Master_Incident_Number esriFieldTypeString(20), Response_Date esriFieldTypeDate, Jurisdiction esriFieldTypeString(30), Division esriFieldTypeString(30), Response_Area esriFieldTypeString(30), Response_Plan esriFieldTypeString(30), Incident_Type esriFieldTypeString(30), Problem esriFieldTypeString(30), Priority_Number esriFieldTypeInteger, Priority_Description esriFieldTypeString(30), Location_Name esriFieldTypeString(400), Address esriFieldTypeString(400), Apartment esriFieldTypeString(10), City esriFieldTypeString(35), State esriFieldTypeString(5), Postal_Code esriFieldTypeString(10), County esriFieldTypeString(30), Location_Type esriFieldTypeString(30), Longitude esriFieldTypeDouble, Latitude esriFieldTypeDouble, Map_Info esriFieldTypeString(10), Cross_Street esriFieldTypeString(400), Time_CallClosed esriFieldTypeDate, EMD_Used esriFieldTypeSmallInteger, Determinant esriFieldTypeString(10), Building esriFieldTypeString(10), Call_Is_Active esriFieldTypeInteger, CallCode esriFieldTypeString(10),
      DeterminantCode esriFieldTypeString(10), Status esriFieldTypeString(8), Symbology esriFieldTypeString(8), Units esriFieldTypeString(200), Appr_Divs esriFieldTypeString(200)
Note: Confire New Incidents Inserted
Dashboard_Incidents (writer ARCGISONLINEFEATURES_6)
    attributes: ID esriFieldTypeInteger, Master_Incident_Number esriFieldTypeString(20), Response_Date esriFieldTypeDate, Jurisdiction esriFieldTypeString(30), Division esriFieldTypeString(30), Response_Area esriFieldTypeString(30), Response_Plan esriFieldTypeString(30), Incident_Type esriFieldTypeString(30), Problem esriFieldTypeString(30), Priority_Number esriFieldTypeInteger, Priority_Description esriFieldTypeString(30), Location_Name esriFieldTypeString(400), Address esriFieldTypeString(400), Apartment esriFieldTypeString(10), City esriFieldTypeString(35), State esriFieldTypeString(5), Postal_Code esriFieldTypeString(10), County esriFieldTypeString(30), Location_Type esriFieldTypeString(30), Longitude esriFieldTypeDouble, Latitude esriFieldTypeDouble, Map_Info esriFieldTypeString(10), Cross_Street esriFieldTypeString(400), Time_CallClosed esriFieldTypeDate, EMD_Used esriFieldTypeSmallInteger, Determinant esriFieldTypeString(10), Building esriFieldTypeString(10), Call_Is_Active esriFieldTypeInteger, CallCode esriFieldTypeString(10), DeterminantCode esriFieldTypeString(10),
      Status esriFieldTypeString(8), Symbology esriFieldTypeString(8), Units esriFieldTypeString(200), Appr_Divs esriFieldTypeString(200)
Note: Push New Incidents to Public Dashboard
Dashboard_Incidents (writer ARCGISONLINEFEATURES_8)
    attributes: Master_Incident_Number esriFieldTypeString(20), Response_Date esriFieldTypeDate, Jurisdiction esriFieldTypeString(30), Division esriFieldTypeString(30), City esriFieldTypeString(35), State esriFieldTypeString(5), County esriFieldTypeString(30), Cross_Street esriFieldTypeString(400), Determinant esriFieldTypeString(10), CallCode esriFieldTypeString(10), DeterminantCode esriFieldTypeString(10), Symbology esriFieldTypeString(8), Units esriFieldTypeString(200), Appr_Divs esriFieldTypeString(200), DayofWeek esriFieldTypeString(10), NumofWeek esriFieldTypeInteger, MTime esriFieldTypeString(10)
Note: Confire Duplicates Deleted
Dashboard_Incidents (writer ARCGISONLINEFEATURES_5)
    attributes: OBJECTID esriFieldTypeOID, ID esriFieldTypeInteger, Master_Incident_Number esriFieldTypeString(20), Response_Date esriFieldTypeDate, Jurisdiction esriFieldTypeString(30), Division esriFieldTypeString(30), Response_Area esriFieldTypeString(30), Response_Plan esriFieldTypeString(30), Incident_Type esriFieldTypeString(30), Problem esriFieldTypeString(30), Priority_Number esriFieldTypeInteger, Priority_Description esriFieldTypeString(30), Location_Name esriFieldTypeString(400), Address esriFieldTypeString(400), Apartment esriFieldTypeString(10), City esriFieldTypeString(35), State esriFieldTypeString(5), Postal_Code esriFieldTypeString(10), County esriFieldTypeString(30), Location_Type esriFieldTypeString(30), Longitude esriFieldTypeDouble, Latitude esriFieldTypeDouble, Map_Info esriFieldTypeString(10), Cross_Street esriFieldTypeString(400), Time_CallClosed esriFieldTypeDate, EMD_Used esriFieldTypeSmallInteger, Determinant esriFieldTypeString(10), Building esriFieldTypeString(10), Call_Is_Active esriFieldTypeInteger, CallCode esriFieldTypeString(10),
      DeterminantCode esriFieldTypeString(10), Status esriFieldTypeString(8), Symbology esriFieldTypeString(8), Units esriFieldTypeString(200), Appr_Divs esriFieldTypeString(200)
Note: Confire Apparatus Updated
Dashboard_Apparatus (writer ARCGISONLINEFEATURES_7)
    attributes: OBJECTID esriFieldTypeOID, Master_Incident_Number esriFieldTypeString(20), Response_Date esriFieldTypeDate, Division esriFieldTypeString(30), Radio_Name esriFieldTypeString(20), Longitude esriFieldTypeDouble, Latitude esriFieldTypeDouble, Hour_ esriFieldTypeSmallInteger, Inc_Division esriFieldTypeString(30)
Note: Confire New Apparatus Inserted
Dashboard_Apparatus (writer ARCGISONLINEFEATURES_6)
    attributes: Master_Incident_Number esriFieldTypeString(20), Response_Date esriFieldTypeDate, Division esriFieldTypeString(30), Radio_Name esriFieldTypeString(20), Longitude esriFieldTypeDouble, Latitude esriFieldTypeDouble, Hour_ esriFieldTypeSmallInteger, Inc_Division esriFieldTypeString(30)
Note: Push New Apparatuss to Public Dashboard
Dashboard_Apparatus (writer ARCGISONLINEFEATURES_9)
    attributes: DayofWeek esriFieldTypeString(10), NumofWeek esriFieldTypeInteger, Master_Incident_Number esriFieldTypeString(20), Response_Date esriFieldTypeDate, Division esriFieldTypeString(30), Radio_Name esriFieldTypeString(20), Inc_Division esriFieldTypeString(30), Hour_ esriFieldTypeSmallInteger, MTime esriFieldTypeString(10)
Note: Confire Apparatus Duplicates Deleted
Dashboard_Apparatus (writer ARCGISONLINEFEATURES_5)
    attributes: OBJECTID esriFieldTypeOID, Master_Incident_Number esriFieldTypeString(20), Response_Date esriFieldTypeDate, Division esriFieldTypeString(30), Radio_Name esriFieldTypeString(20), Longitude esriFieldTypeDouble, Latitude esriFieldTypeDouble, Hour_ esriFieldTypeSmallInteger, Inc_Division esriFieldTypeString(30)

FME custom transformer Incident Coordinate Fix

Parameters:
- LONGITUDE = @Value(Longitude)   # Longitude
- LATITUDE = @Value(Latitude)   # Latitude

Stripped_Lat_Front_Input (input)
    -> Stripped_Lat_Front
Stripped_Lat_Front: SubstringExtractor
    START = 0
    RESULT_ATTR = front
    END = 1
    SRC_ATTR = Latitude
    -> Stripped_Lat_Back
Stripped_Lat_Back: SubstringExtractor
    START = 2
    RESULT_ATTR = back
    END = -1
    SRC_ATTR = Latitude
    -> StringConcatenator_Lat
StringConcatenator_Lat
    VAL_ATTR = Latitude
    ACTION = Create New Attribute
    PARM_LINE = @Value(front).@Value(back)
    -> Stripped_Long_Front
Stripped_Long_Front: SubstringExtractor
    START = 0
    RESULT_ATTR = front
    END = 2
    SRC_ATTR = Longitude
    -> Stripped_Long_Back
Stripped_Long_Back: SubstringExtractor
    START = 3
    RESULT_ATTR = back
    END = -1
    SRC_ATTR = Longitude
    -> StringConcatenator_Long
StringConcatenator_Long
    VAL_ATTR = Longitude
    ACTION = Create New Attribute
    PARM_LINE = -@Value(front).@Value(back)
    -> AttributeRemover
AttributeRemover
    REMOVE_ATTRS = back,front
    -> AttributeRemover_Output (output)
AttributeRemover_Output (output)

FME custom transformer UTC Converter

Parameters:
- RESPONSE_DATE = @Value(Response_Date)   # Response Date

DateFormatter_7_Input (input)
    -> DateFormatter_7
DateFormatter_7
    SRCFMT = Unknown - Automatic Detection
    INVALID_DATE_VALUE = _FME_NO_OP_
    FMT = FME Date/Time (%Y%m%d%H%M%S)
    DATE_ATTR = Response_Date
    -> TCLCaller_4
TCLCaller_4
    VAL_ATTR = Response_Date
    TCLPROG = formatDate
    SRC:
      # Safe Software Inc. 2011 MAS
      # Format a date, optionally adjusting the local timezone
       #  http://tmml.sourceforge.net/doc/tcl/clock.html#SECTid81f75c0
       # http://wiki.tcl.tk/1035
       # Could get this to work using -gmt -8 - always set the the time to a 12 hr clock so using clock add instead
       #

       proc formatDate {} {
       # this attribute matches the FME feature attribute
          set date [FME_GetAttribute Response_Date]

         # puts "date GMT $date"
          # convert to clock seconds
          set t [clock scan $date -format {%Y%m%d%H%M%S} -timezone :America/Los_Angeles ]

         # puts "t     $t"
         # switch to the new timezone and format the date
         set datetime [clock format $t -format {%Y%m%d%H%M%S} -timezone :UTC ]

        # puts  "date MST  $datetime"

         return $datetime
       }
    -> TCLCaller_4_Output (output)
TCLCaller_4_Output (output)

FME custom transformer UnitCreator

Parameters:
- VEHICLE_RADIO_NAME = @Value(VEHICLE Radio_Name)   # Vehicle radio Name
- MASTER_INCIDENT_NUMBER = @Value(Master_Incident_Number)   # Master Incident Number
- VEHICLE_DIVISION = @Value(VEHICLE Division)   # VEHICLE Division

AttributeRenamer_ApparatusID_Input (input)
    -> ListBuilder
ListBuilder
    LIST_NAME = _list
    GRP_BY = Master_Incident_Number
    -> ListConcatenator
ListConcatenator
    VAL_ATTR = Units
    DROP_EMPTY_PARTS = Yes
    SEP = ", "
    LIST_ATTR = _list{}.VEHICLE Radio_Name
    -> ListDuplicateRemover
ListDuplicateRemover
    SRC_LIST = _list{}.VEHICLE Division
    -> ListConcatenator_2
ListConcatenator_2
    VAL_ATTR = Appr_Divs
    DROP_EMPTY_PARTS = Yes
    SEP = ", "
    LIST_ATTR = _list{}.VEHICLE Division
    -> AttributeRemover_2
AttributeRemover_2
    REMOVE_ATTRS = _list{0}.Master_Incident_Number,_list{0}.VEHICLE Division,_list{0}.VEHICLE Radio_Name
    LIST_ATTRS = _list{} _list{}.Master_Incident_Number _list{}.VEHICLE Division _list{}.VEHICLE Radio_Name
    -> AttributeRemover_2_Output (output)
AttributeRemover_2_Output (output)

FME custom transformer DashboardAttributeCreator

Parameters:
- CALL_IS_ACTIVE = @Value(Call_Is_Active)   # Call Is Active
- INCIDENT_TYPE = @Value(Incident_Type)   # Incident Type
- EMD_USED = @Value(EMD_Used)   # Emd Used
- DETERMINANT = @Value(Determinant)   # Determinant

AttributeCreator_Input (input)
    -> AttributeCreator
AttributeCreator
    ATTR_LIST = CallCode,"FME_CONDITIONAL:DEFAULT_VALUE'EMS'BOOL_OP;COMPOSITE;COMPOSITE_TEST;1 AND 2 OR 3 OR 4 OR 5 OR 6 OR 7 OR 8 OR 9 OR 10 OR 11 OR 12 OR 13 OR 14 OR 15 OR 16 OR 17 OR 18 OR 19 OR 20;TEST @Value(EMD_Used) = 0;TEST @Value(Incident_Type) = FC;TEST @Value(Incident_Type) = FS;TEST @Value(Incident_Type) = FG;TEST @Value(Incident_Type) = FT;TEST @Value(Incident_Type) = FV;TEST @Value(Incident_Type) = FD;TEST @Value(Incident_Type) = FI;TEST @Value(Incident_Type) = FR;TEST @Value(Incident_Type) = FU;TEST @Value(Incident_Type) = FC;TEST @Value(Incident_Type) = FWI;TEST @Value(Incident_Type) = BT;TEST @Value(Incident_Type) = CA;TEST @Value(Incident_Type) = CI;TEST @Value(Incident_Type) = IN;TEST @Value(Incident_Type) = OI;TEST @Value(Incident_Type) = RA;TEST @Value(Incident_Type) = SP;TEST @Value(Incident_Type) = ZAP'Fire'BOOL_OP;COMPOSITE;COMPOSITE_TEST;1 AND 2 OR 3 OR 4 OR 5 OR 6 OR 7 OR 8 OR 9 OR 10;TEST @Value(EMD_Used) = 0;TEST @Value(Incident_Type) = TE;TEST @Value(Incident_Type) = TEF;TEST @Value(Incident_Type) = TF;TEST @Value(Incident_Type) = TFF;TEST @Value(Incident_Type) = TI;TEST @Value(Incident_Type) = TIF;TEST @Value(Incident_Type) = TOF;TEST @Value(Incident_Type) = TU;TEST @Value(Incident_Type) = TUF'Traffic'BOOL_OP;COMPOSITE;COMPOSITE_TEST;1 AND 2 OR 3 OR 4 OR 5 OR 6;TEST @Value(EMD_Used) = 0;TEST @Value(Incident_Type) = RQ;TEST @Value(Incident_Type) = RQ-B1;TEST @Value(Incident_Type) = RQ-B2;TEST @Value(Incident_Type) = RQ-B3;TEST @Value(Incident_Type) = RQ-D1'Rescue'BOOL_OP;COMPOSITE;COMPOSITE_TEST;1 AND 2 OR 3;TEST @Value(EMD_Used) = 0;TEST @Value(Incident_Type) = CO;TEST @Value(Incident_Type) = HZ'Hazmat'BOOL_OP;COMPOSITE;COMPOSITE_TEST;1 AND 2 OR 3 OR 4 OR 5 OR 6 OR 7 OR 8 OR 9 OR 10 OR 11 OR 12 OR 13;TEST @Value(EMD_Used) = 0;TEST @Value(Incident_Type) = ELEV;TEST @Value(Incident_Type) = GHZ;TEST @Value(Incident_Type) = GMU;TEST @Value(Incident_Type) = PS;TEST @Value(Incident_Type) = RR;TEST @Value(Incident_Type) = RS;TEST @Value(Incident_Type) = WS;TEST @Value(Incident_Type) = GAT;TEST @Value(Incident_Type) = GBP;TEST @Value(Incident_Type) = GMI;TEST @Value(Incident_Type) = GRD;TEST @Value(Incident_Type) = GRF'Other'FME_NUM_CONDITIONS6___",DeterminantCode,"FME_CONDITIONAL:DEFAULT_VALUE'_FME_NO_OP_'BOOL_OP;AND;COMPOSITE_TEST;<Unused>;TEST @Value(EMD_Used) = 1;TEST @Value(Determinant) CONTAINS A'ALPHA'BOOL_OP;AND;COMPOSITE_TEST;<Unused>;TEST @Value(EMD_Used) = 1;TEST @Value(Determinant) CONTAINS B'BRAVO'BOOL_OP;AND;COMPOSITE_TEST;<Unused>;TEST @Value(EMD_Used) = 1;TEST @Value(Determinant) CONTAINS C'CHARLIE'BOOL_OP;AND;COMPOSITE_TEST;<Unused>;TEST @Value(EMD_Used) = 1;TEST @Value(Determinant) CONTAINS D'DELTA'BOOL_OP;AND;COMPOSITE_TEST;<Unused>;TEST @Value(Determinant) CONTAINS E;TEST @Value(EMD_Used) = 1'ECHO'BOOL_OP;AND;COMPOSITE_TEST;<Unused>;TEST @Value(EMD_Used) = 1;TEST Determinant ATTRIBUTE_IS_EMPTY _FME_BLANK_STRING_'OTHER'FME_NUM_CONDITIONS7___",Status,"FME_CONDITIONAL:DEFAULT_VALUE'Closed'BOOL_OP;OR;COMPOSITE_TEST;<Unused>;TEST Call_Is_Active ATTRIBUTE_VALUE_NULL _FME_BLANK_STRING_;TEST @Value(Call_Is_Active) = 1'Open'FME_NUM_CONDITIONS2___"
    -> AttributeCreator_2
AttributeCreator_2
    ATTR_LIST = Symbology,@Value(CallCode)
    -> AttributeCreator_2_Output (output)
AttributeCreator_2_Output (output)

FME custom transformer InitialDataCleanup

Parameters:
- LATITUDE = @Value(Latitude)   # Latitude
- MASTER_INCIDENT_NUMBER = @Value(Master_Incident_Number)   # Master Incident Number
- INCIDENT_TYPE = @Value(Incident_Type)   # Incident Type

RemoveDashFromIncidentNum_Input (input)
    -> RemoveDashFromIncidentNum
RemoveDashFromIncidentNum: StringReplacer
    REGEXP = no
    NO_MATCH = _FME_NO_OP_
    FIND_TEXT = -
    CASE = no
    SRC_ATTRS = Master_Incident_Number
    -> RemoveBlankIncidentsandTests
RemoveBlankIncidentsandTests: Tester
    TEST_MODE = Automatic
    TEST_CLAUSE:
      TEST Master_Incident_Number ATTRIBUTE_IS_EMPTY ""
      TEST Master_Incident_Number ATTRIBUTE_VALUE_NULL ""
      TEST @Value(Latitude) = 0
      TEST Incident_Type ATTRIBUTE_IS_EMPTY ""
      TEST @Value(Incident_Type) = TEST
    BOOL_OP = OR
    TEST_DESCRIPTION = ""
    FAILED -> RemoveBlankIncidentsandTests_Failed (output)
RemoveBlankIncidentsandTests_Failed (output)

FME custom transformer Month Selection

Parameters:
- RESPONSE_DATE = @Value(Response_Date)   # Response Date

DateFormatter_Input (input)
    -> AttributeCreator
AttributeCreator
    ATTR_LIST = Test_Date,12 hours ago
    -> DateFormatter
DateFormatter
    SRCFMT = Unknown - Automatic Detection
    INVALID_DATE_VALUE = FME_NULL_VALUE
    FMT = FME Date/Time (%Y%m%d%H%M%S)
    DATE_ATTR = Response_Date,Test_Date
    -> 6_hours
6_hours: Tester
    TEST_MODE = Automatic
    TEST_CLAUSE = TEST @Value(Response_Date) >= @Value(Test_Date)
    BOOL_OP = OR
    TEST_DESCRIPTION = ""
    PASSED -> AttributeRemover
AttributeRemover
    REMOVE_ATTRS = Test_Date
    -> AttributeCreator_Output (output)
AttributeCreator_Output (output)

FME custom transformer CreateHourAttribute

Parameters:
- RESPONSE_DATE = @Value(Response_Date)   # Response Date

AttributeCreator_3_Input (input)
    -> AttributeCreator_3
AttributeCreator_3
    ATTR_LIST = Hour_,@Value(Response_Date)
    -> DateFormatter_3
DateFormatter_3
    SRCFMT = Unknown - Automatic Detection
    INVALID_DATE_VALUE = _FME_NO_OP_
    FMT = ISO Time (%H)
    DATE_ATTR = Hour_
    -> Strip_Hour
Strip_Hour: SubstringExtractor
    START = 10
    RESULT_ATTR = Hour_
    END = -2
    SRC_ATTR = Hour_
    -> StringFormatter_Hour
StringFormatter_Hour
    FORMAT = d
    SRC_ATTRS = Hour_
    -> StringFormatter_Hour_Output (output)
StringFormatter_Hour_Output (output)

FME custom transformer PullDataFrom12Hours

Parameters:
- RESPONSE_DATE = @Value(Response_Date)   # Response Date

AttributeCreator_5_Input (input)
    -> AttributeCreator_5
AttributeCreator_5
    ATTR_LIST = test_date,12 hours ago
    -> DateFormatter_2
DateFormatter_2
    SRCFMT = Unknown - Automatic Detection
    INVALID_DATE_VALUE = _FME_NO_OP_
    FMT = FME Date/Time (%Y%m%d%H%M%S)
    DATE_ATTR = test_date
    -> Tester_2
Tester_2
    TEST_MODE = Automatic
    TEST_CLAUSE = TEST @Value(Response_Date) >= @Value(test_date)
    BOOL_OP = OR
    TEST_DESCRIPTION = ""
    PASSED -> Tester_2_Passed (output)
Tester_2_Passed (output)
